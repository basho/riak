-- SAMPLE-MIB.mib - Example MIB for Mnesia access.

RIAK DEFINITIONS ::= BEGIN

IMPORTS
        enterprises, Gauge, Counter, IpAddress
                FROM RFC1155-SMI
        DisplayString
                FROM RFC1213-MIB
        OBJECT-TYPE
                FROM RFC-1212;

basho OBJECT IDENTIFIER ::= { enterprises 31130 }
riak OBJECT IDENTIFIER ::= { basho 1 }

vnodeGets OBJECT-TYPE
    SYNTAX Counter
    ACCESS read-only
    STATUS mandatory
    DESCRIPTION
        "Total number of gets performed by all vnodes on node."
    ::= { riak 1 }
vnodePuts OBJECT-TYPE
    SYNTAX Counter
    ACCESS read-only
    STATUS mandatory
    DESCRIPTION
        "Total number of puts performed by all vnodes on node."
    ::= { riak 2 }
nodeGets OBJECT-TYPE
    SYNTAX Counter
    ACCESS read-only
    STATUS mandatory
    DESCRIPTION
        "Number of gets coordinated by node."
    ::= { riak 3 }
nodePuts OBJECT-TYPE
    SYNTAX Counter
    ACCESS read-only
    STATUS mandatory
    DESCRIPTION
        "Number of puts coordinated by node."
    ::= { riak 4 }
nodeGetTimeMean OBJECT-TYPE
    SYNTAX Gauge
    ACCESS read-only
    STATUS mandatory
    DESCRIPTION
        "Mean time in microseconds from starting up a riak_get_fsm to that FSM responding to the client."
    ::= { riak 5 }
nodeGetTimeMedian OBJECT-TYPE
    SYNTAX Gauge
    ACCESS read-only
    STATUS mandatory
    DESCRIPTION
        "Median time in microseconds from starting up a riak_get_fsm to that FSM responding to the client."
    ::= { riak 6 }
nodeGetTime95 OBJECT-TYPE
    SYNTAX Gauge
    ACCESS read-only
    STATUS mandatory
    DESCRIPTION
        "Maximum time in microseconds that from starting up a riak_get_fsm to that FSM responding to the client, for 95% of executions."
    ::= { riak 7 }
nodeGetTime99 OBJECT-TYPE
    SYNTAX Gauge
    ACCESS read-only
    STATUS mandatory
    DESCRIPTION
        "Maximum time in microseconds that from starting up a riak_get_fsm to that FSM responding to the client, for 99% of executions."
    ::= { riak 8 }
nodeGetTime100 OBJECT-TYPE
    SYNTAX Gauge
    ACCESS read-only
    STATUS mandatory
    DESCRIPTION
        "Maximum time in microseconds that from starting up a riak_get_fsm to that FSM responding to the client."
    ::= { riak 9 }
nodePutTimeMean OBJECT-TYPE
    SYNTAX Gauge
    ACCESS read-only
    STATUS mandatory
    DESCRIPTION
        "Mean time in microseconds from starting up a riak_put_fsm to that FSM responding to the client."
    ::= { riak 10 }
nodePutTimeMedian OBJECT-TYPE
    SYNTAX Gauge
    ACCESS read-only
    STATUS mandatory
    DESCRIPTION
        "Median time in microseconds from starting up a riak_put_fsm to that FSM responding to the client."
    ::= { riak 11 }
nodePutTime95 OBJECT-TYPE
    SYNTAX Gauge
    ACCESS read-only
    STATUS mandatory
    DESCRIPTION
        "Maximum time in microseconds that from starting up a riak_put_fsm to that FSM responding to the client, for 95% of executions."
    ::= { riak 12 }
nodePutTime99 OBJECT-TYPE
    SYNTAX Gauge
    ACCESS read-only
    STATUS mandatory
    DESCRIPTION
        "Maximum time in microseconds that from starting up a riak_put_fsm to that FSM responding to the client, for 99% of executions."
    ::= { riak 13 }
nodePutTime100 OBJECT-TYPE
    SYNTAX Gauge
    ACCESS read-only
    STATUS mandatory
    DESCRIPTION
        "Maximum time in microseconds that from starting up a riak_put_fsm to that FSM responding to the client."
    ::= { riak 14 }

END
